module ident {
  yang-version "1.1";
  namespace "urn:example:ident";
  prefix ident;

  import iana-if-type {
    prefix ianaift;
  }

  import ietf-interfaces {
    prefix if;
  }

  organization "Example";
  contact
     "Tel:    +1 724 931 9316";
  description
    "Example of identities";
  reference
    "IEEE 802.1Q";

  revision 2025-02-11 {
    description
      "Example identifies";
  }

  identity ieee8021axLag {
    base ianaift:ieee8023adLag;
    description
      "Another name for ieee8023adLag";
  }


  container bridges {
    description
       "Bridge configuration";
    list bridge {
      key "name";
      description
         "bridge";

      leaf name {
        type string;
        description
          "bridge name";
      }
    }
  }

  augment "/if:interfaces/if:interface" {
    when
      "derived-from-or-self(if:type,'ianaift:ieee8023adLag')" {
      description
        "Applies when a Bridge interface.";
    }
    description
      "Augment the interface model with the Bridge Port";
    container bridge-port {
      description
        "Bridge Port is an extension of the IETF Interfaces model (RFC7223).";

      leaf bridge-name {
        type leafref {
          path '/bridges/bridge/name';
        }
      } 
    }
  }
}
